module ietf-dorms {
    yang-version 1.1;

    namespace "urn:ietf:params:xml:ns:yang:ietf-dorms";
    prefix "dorms";

    import ietf-inet-types {
        prefix "inet";
        reference "RFC 6991 Section 4";
    }

    import ietf-routing-types {
        prefix "rt-types";
        reference "RFC 8294";
    }

    organization "IETF MBONED (Multicast Backbone
        Deployment) Working Group";

    contact
        "Author:   Jake Holland
                   <mailto:jholland@akamai.com>
        ";

    description
    "Copyright (c) 2019 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     This module contains the definition for the DORMS data type.
     It provides out of band metadata about SSM channels.";

    revision 2019-08-25 {
        description "Initial revision.";
        reference
            "I-D.draft-ietf-mboned-dorms";
    }

    container metadata {
        description "Metadata scaffold for source-specific multicast
            channels.";
        list sender {
            key source-address;
            description "Sender for DORMS";

            leaf source-address {
                type inet:ip-address;
                mandatory true;
                description
                    "The source IP address of a multicast sender.";
            }

            list group {
                key group-address;
                description "Metadata for a DORMS (S,G).";

                leaf group-address {
                    type rt-types:ip-multicast-group-address;
                    mandatory true;
                    description "The group IP address for an (S,G).";
                }

                list udp-stream {
                  key "port";
                  description
                      "Metadata for UDP traffic on a specific port.";
                  leaf port {
                      type inet:port-number;
                      mandatory true;
                      description
                          "The UDP port of a data stream.";
                  }
                }
            }
        }
    }
}
